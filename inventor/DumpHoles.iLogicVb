' DumpHoles.iLogicVb — правило iLogic для Autodesk Inventor.
'
' Выгружает координаты, диаметры и глубины всех Hole-элементов (Отверстие,
' Hole feature) открытой детали в CSV — чтобы перенести реальную геометрию
' болванки (крепёжные/контрольные отверстия) в веб-конфигуратор.
'
' Требования к детали: та же система координат, что и у HolderFromCSV —
' центр диска в начале координат, ось диска — Z (эскиз на плоскости XY).
'
' Кроме Hole-элементов дампер вторым проходом разбирает вырезы Extrude/Cut:
'   - круглые (эскиз-окружность) → строка circle с Ø;
'   - фигурные (линии/дуги) → строка contour со списком точек контура
'     (напр. фигурный вырез Mountings). Дуги сэмплируются, сегменты
'     сцепляются по совпадающим концам в замкнутый контур.
' Координаты берутся через SketchToModelSpace, поэтому плоскость эскиза
' может быть любой. Fillet/Chamfer (фаска) и Emboss (гравировка) НЕ
' обрабатываются — гравировку вносим в каталог вручную.
'
' Формат CSV (";" разделитель, "." десятичная точка, единицы — мм):
'   holes-dump;1
'   part;{имя детали}
'   columns;name;x;y;diameter;depth;type;extra1;extra2;tapped
'   {имя};{x};{y};{d};{depth или "through"};{drilled|counterbore|countersink};{extra1};{extra2};{yes|no}
'   contour;{имя};{depth или "through"};x1;y1;x2;y2;...   — фигурный вырез
' extra1/extra2: для counterbore — Ø зенковки; глубина зенковки;
'                для countersink — Ø зенковки; угол, °.
' Одна строка Hole-элемента с несколькими центрами (массив/несколько точек
' эскиза) даёт несколько строк CSV — имя дополняется индексом (-1, -2, …).
'
' Диаметр и координаты читаются надёжно (стандартные свойства Inventor).
' Тип/зенковка/резьба — «по возможности»: у разных версий Inventor эти
' свойства называются немного по-разному, поэтому каждое читается отдельно
' через Try/Catch и просто остаётся пустым, если не подошло — остальная
' строка при этом не теряется.

Sub Main()
	If ThisApplication.ActiveDocument Is Nothing OrElse _
	   ThisApplication.ActiveDocument.DocumentType <> DocumentTypeEnum.kPartDocumentObject Then
		MessageBox.Show("Откройте деталь с отверстиями.", "DumpHoles", _
			MessageBoxButtons.OK, MessageBoxIcon.Warning)
		Return
	End If
	Dim doc As PartDocument = ThisApplication.ActiveDocument
	Dim compDef As PartComponentDefinition = doc.ComponentDefinition

	' Object (позднее связывание) — чтобы расхождения в именах свойств между
	' версиями Inventor ловились через Try/Catch, а не валили весь рулесет.
	Dim holeFeats As Object = compDef.Features.HoleFeatures

	Dim inv As System.Globalization.CultureInfo = System.Globalization.CultureInfo.InvariantCulture
	Dim mm As Double = 10.0 ' внутренние единицы Inventor — см → мм
	Dim tg As TransientGeometry = ThisApplication.TransientGeometry
	Dim rows As New List(Of String)
	rows.Add("holes-dump;1")
	rows.Add("part;" & doc.DisplayName.Replace(";", ","))
	rows.Add("columns;name;x;y;diameter;depth;type;extra1;extra2;tapped")

	Dim built As Integer = 0
	For Each hf As Object In holeFeats
		Dim dia As Double = 0
		Try
			dia = CDbl(hf.HoleDiameter.Value) * mm
		Catch
		End Try

		Dim depthStr As String = "through"
		Try
			If CType(hf.ExtentType, Integer) <> PartFeatureExtentEnum.kThroughAllExtent Then
				depthStr = (CDbl(hf.Depth.Value) * mm).ToString("0.###", inv)
			End If
		Catch
		End Try

		' Тип отверстия определяем не по HoleTypeEnum (имена расходятся между
		' версиями Inventor), а по наличию свойств зенковки/цековки: их чтение
		' на обычном сверлёном отверстии просто бросает исключение (Try/Catch).
		Dim cbD As Double = 0, cbDepth As Double = 0
		Try : cbD = CDbl(hf.CounterboreDiameter.Value) * mm : Catch : End Try
		Try : cbDepth = CDbl(hf.CounterboreDepth.Value) * mm : Catch : End Try
		Dim csD As Double = 0, csAng As Double = 0
		Try : csD = CDbl(hf.CountersinkDiameter.Value) * mm : Catch : End Try
		Try : csAng = CDbl(hf.CountersinkAngle.Value) * 180.0 / Math.PI : Catch : End Try

		Dim typeName As String = "drilled"
		Dim extra1 As String = "", extra2 As String = ""
		If cbD > 0 Then
			typeName = "counterbore"
			extra1 = cbD.ToString("0.###", inv)
			extra2 = cbDepth.ToString("0.###", inv)
		ElseIf csD > 0 Then
			typeName = "countersink"
			extra1 = csD.ToString("0.###", inv)
			extra2 = csAng.ToString("0.#", inv)
		End If

		Dim tapped As String = "no"
		Try
			If CBool(hf.Tapped) Then tapped = "yes"
		Catch
		End Try

		Dim centers As Object = hf.HoleCenterPoints
		Dim idx As Integer = 0
		For Each pt As Object In centers
			idx += 1
			' HoleCenterPoints — это SketchPoint'ы: у них нет прямых X/Y,
			' координата лежит в 2D-геометрии эскиза. Переводим её в модельное
			' пространство через родительский эскиз (SketchToModelSpace).
			' Запасной путь — рабочая точка/вершина с 3D-свойством .Point.
			Dim mx As Double = 0, my As Double = 0
			Dim got As Boolean = False
			Try
				Dim g2 As Object = pt.Geometry                 ' Point2d в эскизе
				Dim par As Object = pt.Parent                  ' PlanarSketch
				Dim g3 As Object = par.SketchToModelSpace(g2)  ' Point в модели
				mx = CDbl(g3.X) * mm : my = CDbl(g3.Y) * mm
				got = True
			Catch
			End Try
			If Not got Then
				Try
					Dim g3 As Object = pt.Point                ' WorkPoint/вершина (3D)
					mx = CDbl(g3.X) * mm : my = CDbl(g3.Y) * mm
					got = True
				Catch
				End Try
			End If
			If Not got Then Continue For ' не смогли прочитать центр — пропускаем

			Dim nm As String = CStr(hf.Name).Replace(";", ",")
			If centers.Count > 1 Then nm &= "-" & idx.ToString()
			rows.Add(nm & ";" & mx.ToString("0.###", inv) & ";" & my.ToString("0.###", inv) & ";" & _
				dia.ToString("0.###", inv) & ";" & depthStr & ";" & typeName & ";" & extra1 & ";" & extra2 & ";" & tapped)
			built += 1
		Next
	Next

	' --- второй проход: круглые вырезы Extrude (не через команду «Отверстие») ---
	' Ловим посадки/зоны напыления свидетелей и прочие круглые карманы,
	' сделанные эскизом-окружностью + Extrude/Cut. Вспомогательную
	' (construction) геометрию в эскизе игнорируем; несколько рабочих
	' окружностей в одном эскизе дают несколько строк с индексом.
	Dim extrudeFeats As Object = compDef.Features.ExtrudeFeatures
	For Each ef As Object In extrudeFeats
		' только вырезы (Cut) — чтобы не принять тело диска или бобышки за отверстия
		Dim isCut As Boolean = False
		Try
			isCut = (CType(ef.Definition.Operation, Integer) = PartFeatureOperationEnum.kCutOperation)
		Catch
		End Try
		If Not isCut Then Continue For

		Dim sk As Object = Nothing
		Try : sk = ef.Profile.Parent : Catch : End Try
		If sk Is Nothing Then
			Try : sk = ef.Definition.Profile.Parent : Catch : End Try
		End If
		If sk Is Nothing Then Continue For

		Dim depthStr As String = "through"
		Try
			If CType(ef.Definition.ExtentType, Integer) <> PartFeatureExtentEnum.kThroughAllExtent Then
				depthStr = (CDbl(ef.Definition.Extent.Distance.Value) * mm).ToString("0.###", inv)
			End If
		Catch
		End Try

		' собираем только рабочие (не construction) окружности эскиза
		Dim cxs As New List(Of Double)
		Dim cys As New List(Of Double)
		Dim dias As New List(Of Double)
		Try
			For Each circ As Object In sk.SketchCircles
				Dim isConstr As Boolean = False
				Try : isConstr = CBool(circ.Construction) : Catch : End Try
				If isConstr Then Continue For
				Dim c2 As Object = circ.CenterSketchPoint.Geometry
				Dim g3 As Object = sk.SketchToModelSpace(c2)
				cxs.Add(CDbl(g3.X) * mm)
				cys.Add(CDbl(g3.Y) * mm)
				dias.Add(CDbl(circ.Radius) * 2.0 * mm)
			Next
		Catch
		End Try

		Dim baseName As String = CStr(ef.Name).Replace(";", ",")
		For k As Integer = 0 To cxs.Count - 1
			Dim nm As String = baseName
			If cxs.Count > 1 Then nm &= "-" & (k + 1).ToString()
			rows.Add(nm & ";" & cxs(k).ToString("0.###", inv) & ";" & cys(k).ToString("0.###", inv) & ";" & _
				dias(k).ToString("0.###", inv) & ";" & depthStr & ";drilled;;;no")
			built += 1
		Next

		' --- фигурные вырезы: контуры из линий/дуг эскиза (напр. Mountings) ---
		' Собираем сегменты (линии — 2 точки, дуги — сэмплируем), сцепляем по
		' совпадающим концам в замкнутые контуры, выводим строкой:
		'   contour;{имя};{depth|through};x1;y1;x2;y2;...
		Try
			Dim hasNonCircle As Boolean = False
			Try : hasNonCircle = (sk.SketchLines.Count > 0 OrElse sk.SketchArcs.Count > 0) : Catch : End Try
			If hasNonCircle Then
				Dim segs As New List(Of List(Of Double()))
				' линии
				For Each ln As Object In sk.SketchLines
					Dim isC As Boolean = False
					Try : isC = CBool(ln.Construction) : Catch : End Try
					If isC Then Continue For
					Dim seg As New List(Of Double())
					seg.Add(ToModelMM(sk, ln.StartSketchPoint.Geometry, mm))
					seg.Add(ToModelMM(sk, ln.EndSketchPoint.Geometry, mm))
					segs.Add(seg)
				Next
				' дуги — сэмплируем по углу от начала на величину SweepAngle
				For Each ar As Object In sk.SketchArcs
					Dim isCA As Boolean = False
					Try : isCA = CBool(ar.Construction) : Catch : End Try
					If isCA Then Continue For
					Dim segA As New List(Of Double())
					Dim c2 As Object = ar.CenterSketchPoint.Geometry
					Dim s2 As Object = ar.StartSketchPoint.Geometry
					Dim rr As Double = CDbl(ar.Radius)
					Dim a0 As Double = Math.Atan2(CDbl(s2.Y) - CDbl(c2.Y), CDbl(s2.X) - CDbl(c2.X))
					Dim sweep As Double = 0
					Try : sweep = CDbl(ar.SweepAngle) : Catch : End Try
					Dim nS As Integer = 12
					For q As Integer = 0 To nS
						Dim aa As Double = a0 + sweep * q / nS
						Dim p2 As Object = tg.CreatePoint2d(CDbl(c2.X) + rr * Math.Cos(aa), CDbl(c2.Y) + rr * Math.Sin(aa))
						segA.Add(ToModelMM(sk, p2, mm))
					Next
					segs.Add(segA)
				Next

				' сцепка сегментов в контуры по совпадающим концам
				If segs.Count > 0 Then
				Dim used(segs.Count - 1) As Boolean
				Dim tolC As Double = 0.02 ' мм
				For i As Integer = 0 To segs.Count - 1
					If used(i) Then Continue For
					Dim lp As New List(Of Double())
					For Each sp As Double() In segs(i) : lp.Add(sp) : Next
					used(i) = True
					Dim extended As Boolean = True
					Do While extended
						extended = False
						Dim tail As Double() = lp(lp.Count - 1)
						For j As Integer = 0 To segs.Count - 1
							If used(j) Then Continue For
							Dim s As List(Of Double()) = segs(j)
							If Dist2(tail, s(0)) < tolC Then
								For t As Integer = 1 To s.Count - 1 : lp.Add(s(t)) : Next
								used(j) = True : extended = True : Exit For
							ElseIf Dist2(tail, s(s.Count - 1)) < tolC Then
								For t As Integer = s.Count - 2 To 0 Step -1 : lp.Add(s(t)) : Next
								used(j) = True : extended = True : Exit For
							End If
						Next
					Loop
					' убираем дублирующую замыкающую точку
					If lp.Count >= 4 AndAlso Dist2(lp(0), lp(lp.Count - 1)) < tolC Then lp.RemoveAt(lp.Count - 1)
					If lp.Count >= 3 Then
						Dim sb As New System.Text.StringBuilder()
						sb.Append("contour;") : sb.Append(baseName) : sb.Append(";") : sb.Append(depthStr)
						For Each pp As Double() In lp
							sb.Append(";") : sb.Append(pp(0).ToString("0.###", inv))
							sb.Append(";") : sb.Append(pp(1).ToString("0.###", inv))
						Next
						rows.Add(sb.ToString())
						built += 1
					End If
				Next
				End If
			End If
		Catch
			' контур не разобрался — пропускаем, круглые строки уже сохранены
		End Try
	Next

	If built = 0 Then
		MessageBox.Show("Не удалось прочитать ни одного отверстия (ни Hole-элементов, " & _
			"ни простых круглых вырезов Extrude на плоскости XY).", "DumpHoles")
		Return
	End If

	Dim dlg As New System.Windows.Forms.SaveFileDialog()
	dlg.Title = "Сохранить выгрузку отверстий"
	dlg.Filter = "CSV (*.csv)|*.csv"
	dlg.FileName = System.IO.Path.GetFileNameWithoutExtension(doc.DisplayName) & "-holes.csv"
	If dlg.ShowDialog() <> System.Windows.Forms.DialogResult.OK Then Return

	System.IO.File.WriteAllText(dlg.FileName, String.Join(vbCrLf, rows) & vbCrLf, New System.Text.UTF8Encoding(True))
	MessageBox.Show("Готово: выгружено элементов — " & built.ToString() & "." & vbCrLf & dlg.FileName, "DumpHoles")
End Sub

' Точка эскиза (Point2d) → {x, y} в мм модельных координат
Function ToModelMM(sk As Object, pt2d As Object, mm As Double) As Double()
	Dim g3 As Object = sk.SketchToModelSpace(pt2d)
	Return New Double() {CDbl(g3.X) * mm, CDbl(g3.Y) * mm}
End Function

' Расстояние между двумя точками {x, y}
Function Dist2(a As Double(), b As Double()) As Double
	Return Math.Sqrt((a(0) - b(0)) * (a(0) - b(0)) + (a(1) - b(1)) * (a(1) - b(1)))
End Function
