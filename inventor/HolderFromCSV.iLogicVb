' HolderFromCSV - правило iLogic для Autodesk Inventor (формат CSV v4).
'
' Читает CSV из веб-конфигуратора и вырезает в ОТКРЫТОЙ детали (болванке диска)
' реальные карманы под детали и контрольные отверстия:
'   * посадка (seat)          - глухой вырез на глубину depth от верхней грани;
'   * паз под пинцет (slot)    - глухой вырез на ту же глубину (если включён);
'   * зона напыления (CA)      - сквозной вырез меньшего контура на дне посадки;
'   * метки-ориентиры (mark)   - маленькие конические зенковки Ø/угол из строки
'     "mark" CSV, только у ДЕТАЛЕЙ с пазом (не у контрольных отверстий).
'     Количество меток = markCount = номер разновидности детали в заказе
'     (1-я деталь - одна метка, 2-я - две, и т.д.) - нужно отличать похожие по
'     размеру детали и метить ориентацию у форм, где это важно. Первая метка -
'     в точке (markX, markY), остальные - дальше вдоль паза с шагом markPitch
'     (см. export-csv.js).
' Плюс обновляет гравировку (Emboss) двумя строками из формы заказа - номер и
' название подложкодержателя, в геометрический текст (Sketch Text) внутри
' эскизов "Sketch9" (вложен в Emboss "PartNumber") и "Sketch10" (вложен в
' Emboss "PartDimensions") - имена эскизов зашиты строками в вызовах
' SetEmbossText в конце Main(); при переименовании в Inventor поправьте их.
' Само тело диска правило не строит.
'
' CSV v2 (18 колонок, без markX/markY/markCount и без строки "mark") и v3
' (markX/markY есть, но без markCount и без шага в строке "mark") тоже
' читаются - для v2 метки не строятся, для v3 везде считается ровно 1 метка.
'
' Требования к болванке:
'   - диск построен с центром в начале координат XY;
'   - ось диска - ось Z (плоский диск). Карманы режутся от верхней грани вниз (-Z);
'   - в болванке уже есть эскизы "Sketch9"/"Sketch10" со Sketch Text внутри
'     (вложены в Emboss-фичи PartNumber/PartDimensions) - правило только
'     меняет их текст, не создаёт их.
'
' Установка: Inventor -> Управление -> iLogic -> создать правило (или внешнее
' правило) и вставить этот код целиком. При запуске правило спросит CSV и,
' если в файле есть контрольные отверстия, - строить их или пропустить.

Sub Main()
	If ThisApplication.ActiveDocument Is Nothing OrElse _
	   ThisApplication.ActiveDocument.DocumentType <> DocumentTypeEnum.kPartDocumentObject Then
		MessageBox.Show("Откройте деталь - болванку диска.", "HolderFromCSV", _
			MessageBoxButtons.OK, MessageBoxIcon.Warning)
		Return
	End If
	Dim doc As PartDocument = ThisApplication.ActiveDocument
	Dim compDef As PartComponentDefinition = doc.ComponentDefinition
	If compDef.SurfaceBodies.Count = 0 Then
		MessageBox.Show("В детали нет тела - сначала постройте диск.", "HolderFromCSV", _
			MessageBoxButtons.OK, MessageBoxIcon.Warning)
		Return
	End If

	' --- выбор CSV ---
	Dim dlg As New System.Windows.Forms.OpenFileDialog()
	dlg.Title = "Выберите CSV из конфигуратора"
	dlg.Filter = "CSV конфигуратора (*.csv)|*.csv|Все файлы (*.*)|*.*"
	If dlg.ShowDialog() <> System.Windows.Forms.DialogResult.OK Then Return

	Dim inv As System.Globalization.CultureInfo = System.Globalization.CultureInfo.InvariantCulture
	Dim lines() As String = System.IO.File.ReadAllLines(dlg.FileName)

	' --- разбор файла ---
	Dim discDia As Double = 0
	Dim discThk As Double = 0
	Dim holderNo As String = "", holderName As String = ""
	Dim markD As Double = 2, markAngle As Double = 90, markPitch As Double = 4 ' по умолчанию - на случай CSV v2/v3
	Dim rows As New List(Of String())
	Dim dataStarted As Boolean = False
	For Each rawLine As String In lines
		Dim t As String = rawLine.Trim().TrimStart(ChrW(65279)) ' срезаем BOM
		If t = "" Then Continue For
		Dim f() As String = t.Split(";"c)
		If dataStarted Then
			If f.Length >= 18 Then rows.Add(f)
		ElseIf f(0) = "disc" AndAlso f.Length >= 4 Then
			discDia = ParseNum(f(3), inv)
			If f.Length >= 5 Then discThk = ParseNum(f(4), inv)
		ElseIf f(0) = "holder" AndAlso f.Length >= 3 Then
			holderNo = f(1)
			holderName = f(2)
		ElseIf f(0) = "mark" AndAlso f.Length >= 3 Then
			markD = ParseNum(f(1), inv)
			markAngle = ParseNum(f(2), inv)
			If f.Length >= 4 Then markPitch = ParseNum(f(3), inv)
		ElseIf f(0) = "columns" Then
			dataStarted = True
		End If
	Next
	If rows.Count = 0 Then
		MessageBox.Show("В файле не найдено данных. Это CSV из конфигуратора (формат v2)?", _
			"HolderFromCSV", MessageBoxButtons.OK, MessageBoxIcon.Warning)
		Return
	End If

	' --- контрольные отверстия: строить или пропустить ---
	Dim hasControl As Boolean = False
	For Each f() As String In rows
		If f(0) = "control" Then hasControl = True : Exit For
	Next
	Dim buildControl As Boolean = False
	If hasControl Then
		buildControl = InputRadioBox("Контрольные отверстия:", _
			"Строить из CSV", "Не строить (уже есть в болванке)", False, "HolderFromCSV")
	End If

	' --- сверка диаметра болванки с CSV (внутренние единицы Inventor - см) ---
	Dim rb As Box = compDef.SurfaceBodies.Item(1).RangeBox
	Dim curDia As Double = Math.Max(rb.MaxPoint.X - rb.MinPoint.X, rb.MaxPoint.Y - rb.MinPoint.Y) * 10.0
	If discDia > 0 AndAlso Math.Abs(curDia - discDia) > 0.05 Then
		If MessageBox.Show("Диаметр открытого диска: " & curDia.ToString("0.##") & " мм," & vbCrLf & _
			"в CSV указан: " & discDia.ToString("0.##") & " мм." & vbCrLf & vbCrLf & "Продолжить?", _
			"HolderFromCSV", MessageBoxButtons.YesNo, MessageBoxIcon.Warning) <> _
			System.Windows.Forms.DialogResult.Yes Then Return
	End If

	Dim tg As TransientGeometry = ThisApplication.TransientGeometry
	Dim mm As Double = 0.1 ' мм -> см
	Dim thk As Double = (rb.MaxPoint.Z - rb.MinPoint.Z) ' толщина диска, см
	Dim defDepth As Double = Math.Max(0.05, thk - 0.15) ' запасная глубина ~ толщина-1.5мм

	' --- плоскость реза = верхняя грань диска (Z макс), нормаль +Z, режем в -Z ---
	Dim topZ As Double = rb.MaxPoint.Z
	Dim cutPlane As WorkPlane = compDef.WorkPlanes.Item(3) ' XY
	If Math.Abs(topZ) > 0.0001 Then
		Dim wp As WorkPlane = compDef.WorkPlanes.AddByPlaneAndOffset(compDef.WorkPlanes.Item(3), topZ)
		wp.Visible = False
		cutPlane = wp
	End If

	' контуры собираем в эскизы: посадки/пазы - по глубине, зона напыления - в один
	Dim seatByDepth As New Dictionary(Of Double, PlanarSketch)
	Dim slotByDepth As New Dictionary(Of Double, PlanarSketch)
	Dim caSketch As PlanarSketch = Nothing
	Dim markSketch As PlanarSketch = Nothing
	Dim idx As Integer = 0
	Dim nSeat As Integer = 0, nSlot As Integer = 0, nCA As Integer = 0, nMark As Integer = 0
	Dim stage As String = "разбор"

	Try
		For Each f() As String In rows
			Dim kind As String = f(0)
			Dim typ As String = f(1)
			If kind = "control" AndAlso Not buildControl Then Continue For
			stage = "контур " & kind & "/" & typ & " @ " & f(2) & "," & f(3)

			Dim cx As Double = ParseNum(f(2), inv) * mm
			Dim cy As Double = ParseNum(f(3), inv) * mm
			Dim dd As Double = ParseNum(f(4), inv) * mm
			Dim w As Double = ParseNum(f(5), inv) * mm
			Dim h As Double = ParseNum(f(6), inv) * mm
			Dim ch As Double = ParseNum(f(7), inv) * mm
			Dim rot As Double = ParseNum(f(8), inv)
			Dim seatD As Double = ParseNum(f(9), inv) * mm
			Dim caDia As Double = ParseNum(f(10), inv) * mm
			Dim seatGap As Double = ParseNum(f(11), inv) * mm
			Dim caInset As Double = ParseNum(f(12), inv) * mm
			Dim slotOn As Boolean = (f(13) = "1")
			Dim slotAngle As Double = ParseNum(f(14), inv)
			Dim slotL As Double = ParseNum(f(15), inv) * mm
			Dim slotW As Double = ParseNum(f(16), inv) * mm
			Dim depth As Double = ParseNum(f(17), inv) * mm
			If depth <= 0 Then depth = defDepth
			If depth > thk Then depth = thk
			Dim dkey As Double = Math.Round(depth, 4)
			Dim markXs As String = If(f.Length > 18, f(18), "")
			Dim markYs As String = If(f.Length > 19, f(19), "")
			' markCount: если колонки нет (CSV v3), но точка метки есть - считаем
			' 1 метку (как раньше); нет точки - 0.
			Dim markCount As Integer = 0
			If f.Length > 20 AndAlso f(20) <> "" Then
				markCount = CInt(ParseNum(f(20), inv))
			ElseIf markXs <> "" AndAlso markYs <> "" Then
				markCount = 1
			End If

			' --- посадка (глухой вырез на глубину) ---
			Dim seatSk As PlanarSketch = GetSketch(compDef, cutPlane, seatByDepth, dkey, "HFC_seat", idx)
			If typ = "circle" Then
				If seatD > 0 Then AddCircle(seatSk, tg, cx, cy, seatD / 2) : nSeat += 1
			Else
				If AddShape(seatSk, tg, typ, cx, cy, w + 2 * seatGap, h + 2 * seatGap, ch, rot) Then nSeat += 1
			End If

			' --- паз под пинцет (глухой, на ту же глубину) ---
			If slotOn AndAlso slotL > 0 AndAlso slotW > 0 Then
				Dim slotSk As PlanarSketch = GetSketch(compDef, cutPlane, slotByDepth, dkey, "HFC_slot", idx)
				AddStadium(slotSk, tg, cx, cy, slotAngle, slotL, slotW)
				nSlot += 1
			End If

			' --- метки-ориентиры (маленькие конические зенковки), только у деталей.
			' Первая - в (markX, markY), остальные - дальше вдоль паза (slotAngle)
			' с шагом markPitch, той же техникой поворота, что и SlotPt/AddStadium. ---
			If kind = "part" AndAlso markCount > 0 AndAlso markXs <> "" AndAlso markYs <> "" Then
				If markSketch Is Nothing Then markSketch = NewSketch(compDef, cutPlane, "HFC_mark", idx)
				Dim mx0 As Double = ParseNum(markXs, inv) * mm
				Dim my0 As Double = ParseNum(markYs, inv) * mm
				Dim mAr As Double = slotAngle * Math.PI / 180
				Dim mCos As Double = Math.Cos(mAr), mSin As Double = Math.Sin(mAr)
				Dim mPitchCm As Double = markPitch * mm
				For mk As Integer = 0 To markCount - 1
					AddCircle(markSketch, tg, mx0 + mk * mPitchCm * mCos, my0 + mk * mPitchCm * mSin, markD * mm / 2)
					nMark += 1
				Next
			End If

			' --- зона напыления (сквозной вырез меньшего контура) ---
			If typ = "circle" Then
				If caDia > 0 Then
					If caSketch Is Nothing Then caSketch = NewSketch(compDef, cutPlane, "HFC_ca", idx)
					AddCircle(caSketch, tg, cx, cy, caDia / 2)
					nCA += 1
				End If
			Else
				If caInset > 0 AndAlso (w - 2 * caInset) > 0 AndAlso (h - 2 * caInset) > 0 Then
					If caSketch Is Nothing Then caSketch = NewSketch(compDef, cutPlane, "HFC_ca", idx)
					If AddShape(caSketch, tg, typ, cx, cy, w - 2 * caInset, h - 2 * caInset, ch, rot) Then nCA += 1
				End If
			End If
		Next

		If nSeat = 0 AndAlso nCA = 0 Then
			MessageBox.Show("Нечего строить: все элементы пропущены.", "HolderFromCSV")
			Return
		End If

		' --- резы: посадки и пазы глухие (в -Z), зона напыления - насквозь ---
		For Each kv As KeyValuePair(Of Double, PlanarSketch) In seatByDepth
			stage = "рез посадок, глубина " & (kv.Key * 10).ToString("0.##") & " мм"
			CutBlind(compDef, kv.Value, kv.Key)
		Next
		For Each kv As KeyValuePair(Of Double, PlanarSketch) In slotByDepth
			stage = "рез пазов, глубина " & (kv.Key * 10).ToString("0.##") & " мм"
			CutBlind(compDef, kv.Value, kv.Key)
		Next
		If caSketch IsNot Nothing AndAlso nCA > 0 Then
			stage = "рез зоны напыления"
			CutThrough(compDef, caSketch)
		End If
		If markSketch IsNot Nothing AndAlso nMark > 0 Then
			stage = "рез меток-ориентиров"
			CutCountersink(compDef, markSketch, markD * mm, markAngle)
		End If
	Catch ex As Exception
		MessageBox.Show("Ошибка построения [" & stage & "]: " & ex.Message, "HolderFromCSV", _
			MessageBoxButtons.OK, MessageBoxIcon.Error)
		Return
	End Try

	' --- гравировка (Emboss): номер и название подложкодержателя из CSV.
	' Берём эскиз НАПРЯМУЮ по имени (Sketch9/Sketch10 — вложены под Emboss
	' "PartNumber"/"PartDimensions" в дереве), а не через Emboss-фичу: путь
	' feat.Definition.Profile.Parent (рабочий для Extrude) для Emboss не дал
	' эскиз. Если переименуете эти эскизы в Inventor — поменяйте имена и тут.
	' Отдельно от резов и без исключений — если гравировка не найдётся,
	' отверстия уже построены, их терять не нужно; проблема попадёт в
	' итоговое сообщение.
	Dim embossWarn As New List(Of String)
	If holderNo <> "" Then SetEmbossText(compDef, "Sketch9", holderNo, embossWarn)
	If holderName <> "" Then SetEmbossText(compDef, "Sketch10", holderName, embossWarn)

	' Update() пересчитывает только фичи, помеченные "грязными" - раз индикатор
	' обновления на Emboss не появляется, значит смена .Text геометрию кривых
	' грязной не помечает вовсе. Rebuild() пересчитывает дерево целиком, без
	' оглядки на эти флаги - пробуем его как более сильное средство.
	Try
		doc.Rebuild()
	Catch
		doc.Update()
	End Try
	Dim msg As String = "Готово. Посадок: " & nSeat.ToString() & _
		", зон напыления: " & nCA.ToString() & ", пазов: " & nSlot.ToString() & _
		", меток: " & nMark.ToString() & "."
	If embossWarn.Count > 0 Then msg &= vbCrLf & vbCrLf & "Гравировка — проблемы: " & String.Join("; ", embossWarn)
	MessageBox.Show(msg, "HolderFromCSV")
End Sub

' Обновляет текст геометрической гравировки (Sketch Text) в эскизе sketchName.
' Полностью защищено Try/Catch (Object, позднее связывание) - при любой
' проблеме добавляет понятную запись в warnings и не бросает исключение,
' чтобы не потерять уже построенные отверстия.
Sub SetEmbossText(compDef As PartComponentDefinition, sketchName As String, newText As String, warnings As List(Of String))
	Dim sk As Object = Nothing
	Try : sk = compDef.Sketches.Item(sketchName) : Catch : End Try
	If sk Is Nothing Then
		warnings.Add("не найден эскиз «" & sketchName & "»")
		Return
	End If
	Dim tb As Object = Nothing
	Try : tb = sk.TextBoxes.Item(1) : Catch : End Try
	If tb Is Nothing Then
		warnings.Add("в эскизе «" & sketchName & "» не найден текстовый объект (TextBoxes)")
		Return
	End If
	Try
		' Мало войти в редактирование ЭСКИЗА - кривые Geometry Text (по которым
		' режет Emboss) пересчитываются только когда закрывается редактирование
		' САМОГО текстового объекта (как если вручную открыть его двойным
		' кликом и нажать OK в диалоге). Пробуем это по нарастающей: сначала
		' TextBox.Edit()/ExitEdit() (аналог диалога), если такого метода нет -
		' переключение Geometric «моргает» и инвалидирует закэшированные кривые,
		' плюс пишем и FormattedText (иногда именно оно - ведущее поле).
		sk.Edit()
		Dim tbEdited As Boolean = False
		Try
			tb.Edit()
			tb.Text = newText
			tb.ExitEdit()
			tbEdited = True
		Catch
		End Try
		If Not tbEdited Then
			tb.Text = newText
			Try : tb.FormattedText = newText : Catch : End Try
			Try
				Dim wasGeom As Boolean = tb.Geometric
				tb.Geometric = Not wasGeom
				tb.Geometric = wasGeom
			Catch
			End Try
		End If
		sk.ExitEdit()
	Catch ex As Exception
		warnings.Add("«" & sketchName & "»: " & ex.Message)
	End Try
End Sub

' ---------- вспомогательные ----------

Function ParseNum(s As String, inv As System.Globalization.CultureInfo) As Double
	If s Is Nothing OrElse s.Trim() = "" Then Return 0
	Dim v As Double
	If Double.TryParse(s, System.Globalization.NumberStyles.Any, inv, v) Then Return v
	Return 0
End Function

Function NewSketch(compDef As PartComponentDefinition, plane As WorkPlane, prefix As String, ByRef idx As Integer) As PlanarSketch
	Dim sk As PlanarSketch = compDef.Sketches.Add(plane)
	sk.Name = prefix & "_" & idx.ToString()
	idx += 1
	Return sk
End Function

Function GetSketch(compDef As PartComponentDefinition, plane As WorkPlane, dict As Dictionary(Of Double, PlanarSketch), _
		key As Double, prefix As String, ByRef idx As Integer) As PlanarSketch
	If Not dict.ContainsKey(key) Then dict.Add(key, NewSketch(compDef, plane, prefix, idx))
	Return dict(key)
End Function

Sub AddCircle(sk As PlanarSketch, tg As TransientGeometry, cx As Double, cy As Double, r As Double)
	Dim c2d As Point2d = sk.ModelToSketchSpace(tg.CreatePoint(cx, cy, 0))
	sk.SketchCircles.AddByCenterRadius(c2d, r)
End Sub

' Контур прямоугольника/фаски (полилиния) или эллипса (oval). Возвращает True, если добавлен.
Function AddShape(sk As PlanarSketch, tg As TransientGeometry, typ As String, _
		cx As Double, cy As Double, w As Double, h As Double, ch As Double, rotDeg As Double) As Boolean
	If w <= 0 OrElse h <= 0 Then Return False

	If typ = "oval" Then
		Dim majorR As Double = Math.Max(w, h) / 2
		Dim minorR As Double = Math.Min(w, h) / 2
		If minorR <= 0 Then Return False
		If (majorR - minorR) < 0.00001 Then          ' оси равны -> круг (эллипс с равными осями Inventor не примет)
			sk.SketchCircles.AddByCenterRadius(sk.ModelToSketchSpace(tg.CreatePoint(cx, cy, 0)), majorR)
			Return True
		End If
		Dim axDeg As Double = rotDeg
		If h > w Then axDeg = rotDeg + 90
		Dim axRad As Double = axDeg * Math.PI / 180
		Dim c2d As Point2d = sk.ModelToSketchSpace(tg.CreatePoint(cx, cy, 0))
		Dim axPt As Point2d = sk.ModelToSketchSpace(tg.CreatePoint(cx + Math.Cos(axRad), cy + Math.Sin(axRad), 0))
		Dim ddx As Double = axPt.X - c2d.X, ddy As Double = axPt.Y - c2d.Y
		Dim dlen As Double = Math.Sqrt(ddx * ddx + ddy * ddy)
		Dim majorDir As UnitVector2d = tg.CreateUnitVector2d(ddx / dlen, ddy / dlen)
		sk.SketchEllipses.Add(c2d, majorDir, majorR, minorR)
		Return True
	End If

	Dim x As Double = w / 2, y As Double = h / 2
	Dim pts As New List(Of Double())
	If typ = "oct" AndAlso ch > 0 Then
		Dim c As Double = Math.Min(ch, Math.Min(w, h) / 2 - 0.0001)
		pts.Add({-x + c, -y}) : pts.Add({x - c, -y}) : pts.Add({x, -y + c}) : pts.Add({x, y - c})
		pts.Add({x - c, y}) : pts.Add({-x + c, y}) : pts.Add({-x, y - c}) : pts.Add({-x, -y + c})
	Else
		pts.Add({-x, -y}) : pts.Add({x, -y}) : pts.Add({x, y}) : pts.Add({-x, y})
	End If
	AddPolyline(sk, tg, cx, cy, rotDeg, pts)
	Return True
End Function

' Стадион (паз): два прямых борта + два НАСТОЯЩИХ полукруглых торца (SketchArc).
'
' Предыдущая попытка настоящих дуг создавала все 4 точки соединения как
' независимые Point2d и потом «сшивала» их GeometricConstraints.AddCoincident —
' этого недостаточно: ограничение совпадения делает точки геометрически
' совпадающими, но НЕ объединяет их в одну вершину для поиска контура, поэтому
' Profiles.AddForSolid контур не находил. Полигоны посадки режутся надёжно
' именно потому, что AddPolyline передаёт следующей линии тот же ОБЪЕКТ
' prevLine.EndSketchPoint, а не координаты точки — точки физически общие.
' Здесь та же техника: каждая дуга берёт стартовой точкой фактический
' EndSketchPoint предыдущего элемента (SketchLines/SketchArcs.AddByTwoPoints и
' .AddByThreePoints принимают SketchPoint наравне с Point2d) — контур замкнут
' общими вершинами без единого constraint, как и у обычных полигонов.
Sub AddStadium(sk As PlanarSketch, tg As TransientGeometry, cx As Double, cy As Double, _
		angleDeg As Double, L As Double, W As Double)
	Dim r As Double = W / 2
	Dim hs As Double = Math.Max(0, L / 2 - r)
	If hs <= 0.00001 Then          ' паз вырождается в круг
		AddCircle(sk, tg, cx, cy, r)
		Return
	End If
	Dim a As Double = angleDeg * Math.PI / 180
	Dim cosA As Double = Math.Cos(a), sinA As Double = Math.Sin(a)
	Dim pBL As Point2d = SlotPt(sk, tg, cx, cy, cosA, sinA, -hs, -r)   ' низ-лево
	Dim pBR As Point2d = SlotPt(sk, tg, cx, cy, cosA, sinA, hs, -r)    ' низ-право
	Dim pR As Point2d = SlotPt(sk, tg, cx, cy, cosA, sinA, hs + r, 0)  ' дальняя точка правого торца
	Dim pTR As Point2d = SlotPt(sk, tg, cx, cy, cosA, sinA, hs, r)     ' верх-право
	Dim pTL As Point2d = SlotPt(sk, tg, cx, cy, cosA, sinA, -hs, r)    ' верх-лево
	Dim pL As Point2d = SlotPt(sk, tg, cx, cy, cosA, sinA, -hs - r, 0) ' дальняя точка левого торца

	Dim l1 As SketchLine = sk.SketchLines.AddByTwoPoints(pBL, pBR)                       ' нижний борт
	Dim a1 As SketchArc = sk.SketchArcs.AddByThreePoints(l1.EndSketchPoint, pR, pTR)     ' правый торец (дуга)
	Dim l2 As SketchLine = sk.SketchLines.AddByTwoPoints(a1.EndSketchPoint, pTL)         ' верхний борт
	sk.SketchArcs.AddByThreePoints(l2.EndSketchPoint, pL, l1.StartSketchPoint)           ' левый торец, замыкает петлю на старт l1
End Sub

' Локальная точка паза (lx,ly) -> точка в координатах эскиза (поворот + перенос).
Function SlotPt(sk As PlanarSketch, tg As TransientGeometry, cx As Double, cy As Double, _
		cosA As Double, sinA As Double, lx As Double, ly As Double) As Point2d
	Dim px As Double = cx + lx * cosA - ly * sinA
	Dim py As Double = cy + lx * sinA + ly * cosA
	Return sk.ModelToSketchSpace(tg.CreatePoint(px, py, 0))
End Function

' Замкнутая полилиния по локальным точкам pts (поворот rotDeg, перенос в cx,cy).
Sub AddPolyline(sk As PlanarSketch, tg As TransientGeometry, cx As Double, cy As Double, _
		rotDeg As Double, pts As List(Of Double()))
	Dim a As Double = rotDeg * Math.PI / 180
	Dim cosA As Double = Math.Cos(a), sinA As Double = Math.Sin(a)
	Dim p2d As New List(Of Point2d)
	For Each p As Double() In pts
		Dim px As Double = cx + p(0) * cosA - p(1) * sinA
		Dim py As Double = cy + p(0) * sinA + p(1) * cosA
		p2d.Add(sk.ModelToSketchSpace(tg.CreatePoint(px, py, 0)))
	Next
	Dim firstLine As SketchLine = sk.SketchLines.AddByTwoPoints(p2d(0), p2d(1))
	Dim prevLine As SketchLine = firstLine
	Dim k As Integer
	For k = 1 To p2d.Count - 2
		prevLine = sk.SketchLines.AddByTwoPoints(prevLine.EndSketchPoint, p2d(k + 1))
	Next
	sk.SketchLines.AddByTwoPoints(prevLine.EndSketchPoint, firstLine.StartSketchPoint)
End Sub

' Глухой вырез на глубину depthCm в направлении -нормаль эскиза (в тело диска).
Sub CutBlind(compDef As PartComponentDefinition, sk As PlanarSketch, depthCm As Double)
	Dim prof As Profile = sk.Profiles.AddForSolid
	Dim exDef As ExtrudeDefinition = compDef.Features.ExtrudeFeatures.CreateExtrudeDefinition( _
		prof, PartFeatureOperationEnum.kCutOperation)
	exDef.SetDistanceExtent(depthCm, PartFeatureExtentDirectionEnum.kNegativeExtentDirection)
	compDef.Features.ExtrudeFeatures.Add(exDef)
End Sub

' Сквозной вырез (симметрично - через всю толщину независимо от ориентации).
Sub CutThrough(compDef As PartComponentDefinition, sk As PlanarSketch)
	Dim prof As Profile = sk.Profiles.AddForSolid
	Dim exDef As ExtrudeDefinition = compDef.Features.ExtrudeFeatures.CreateExtrudeDefinition( _
		prof, PartFeatureOperationEnum.kCutOperation)
	exDef.SetThroughAllExtent(PartFeatureExtentDirectionEnum.kSymmetricExtentDirection)
	compDef.Features.ExtrudeFeatures.Add(exDef)
End Sub

' Метки-ориентиры: конус, сужающийся от диаметра markDiaCm в точке до нуля на
' глубине r/tan(угол/2) - т.е. коническая зенковка заданного угла (90° по
' умолчанию) без цилиндрической части. sk уже содержит по одной окружности
' Ø markDiaCm на каждую метку (см. Main) - режем их ОДНИМ тейпер-экструдом.
'
' ВНИМАНИЕ: знак TaperAngle (сужение внутрь тела, а не расширение наружу) не
' проверен на реальном Inventor - при первом запуске проверьте, что зенковки
' получаются сходящимися конусами, а не растущими проёмами; если наоборот,
' поменяйте знак на противоположный в строке exDef.TaperAngle ниже.
Sub CutCountersink(compDef As PartComponentDefinition, sk As PlanarSketch, markDiaCm As Double, angleDeg As Double)
	Dim halfAngleRad As Double = (angleDeg / 2) * Math.PI / 180
	Dim depthCm As Double = (markDiaCm / 2) / Math.Tan(halfAngleRad)
	Dim prof As Profile = sk.Profiles.AddForSolid
	Dim exDef As ExtrudeDefinition = compDef.Features.ExtrudeFeatures.CreateExtrudeDefinition( _
		prof, PartFeatureOperationEnum.kCutOperation)
	exDef.SetDistanceExtent(depthCm, PartFeatureExtentDirectionEnum.kNegativeExtentDirection)
	exDef.TaperAngle = -halfAngleRad
	compDef.Features.ExtrudeFeatures.Add(exDef)
End Sub
